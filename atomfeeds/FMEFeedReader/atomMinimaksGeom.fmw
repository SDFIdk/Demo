FME workspace atomMinimaksGeom.fmw

Parameters:
- feed = http://download.kortforsyningen.dk/sites/default/files/feeds/MATRIKELKORT_GML.xml   # http://download.kortforsyningen.dk/sites/default/files/feeds/MATRIKELKORT_GML.xml Angiv feed
- pass = atomfe3d   # Angiv kortforsynings pasord
- user = atomfeed   # Angiv bruger navn
- mfRoot = return $::FME_MacroValues(FME_MF_DIR_UNIX)   # Tcl Script
- sidst:   # Tcl Script
      set retval [string trim [read [set f [ open $::FME_MacroValues(FME_MF_DIR_UNIX)/sidsteGang.txt ]]]]
      
      puts $retval
      
      close $f
      
      return $retval
- mitOmraade = $(mfRoot)/data/test.ffs   # angiv søge fil
- tempData = $(mfRoot)/data/tempData.zip   # Angiv temp data fil
- gmlFile = $(mfRoot)/temp/MATRIKEL.gml   # angiv GML file

Readers:
- GEORSS_1: GEORSS from $(feed)

Writers:
- TEXTLINE_1: TEXTLINE to $(mfRoot)\sidsteGang.txt

Note: Eksepme Worksapce der viser hvordan FME kan brugest til / At læse et atom feed / Analysere attributter i forhold til opdatering - ændringer siden sidst / Søge rumligt i forhold til et interesse område / Hente og indlæse de fundne data
Note: LastTime / Gemmer LastUpdate attributten som filen sidsteGang.txt / Værdien af denne indlæses ved næste kørsel i den Private parameter sidst som bruges til at finde ændringer sidne sidste kørsel
Note: Analyse af Feed / Læser alle entrys i feedet og tester for om LastUpdate er større end 'sidst' / Desuden testes om bounding boxen for de fundne ejerlav intersecet en geometri med mit 'interessse' område / Resultate af dette er ændringer siden sidst i mit omåde, disse filer akn vi så hente og arbejde videre med / Med Sampler sikre vi at vi kn henter en data fil
Note: Hent den funde GML fil / Først brugesTclCaller til at tilføje bruger og pasord til url' / Herefter brgues HttpFetcher til at hente zip filen med data / Vi er desværre nødt til at pakke data ud af zip filen dette sker i den andne TclCaller / Endelig bruges FeaturReader til at indlæse data i FME

Bookmark: Write 'LastTime.txt'
Feed (reader GEORSS_1)
    -> Logger
    -> xxxFeed
xxxFeed: Inspector
Logger
    MESSAGE = Feature is:
    MAXFEATS = 20
    MAXCOORDS = 20
    LOGGED -> AttributeRenamer
AttributeRenamer
    ATTR_LIST = LastUpdate,text_line_data,""
    -> text_line (writer TEXTLINE_1)
text_line (writer TEXTLINE_1)
    attributes: text_line_data buffer

Bookmark: Read feed and test date and area
Entry (reader GEORSS_1)
    -> xxAlle
    -> Tester
Tester
    TEST_MODE = Automatic
    TEST_DESCRIPTION = ""
    BOOL_OP = OR
    TEST_CLAUSE = TEST @Value(LastUpdate) > $(sidst)
    PASSED -> SpatialFilter [input 2]
    PASSED -> Opdateret
Opdateret: Inspector
xxAlle: Inspector
Creator_2
    NUM = 1
    GEOMTYPE = Geometry Object
    CREATED -> FeatureReader
FeatureReader
    ATTRIBUTES = MitOmraade,
    FEATURETYPES = MitOmraade
    SUPPORTED_SPATIAL_INTERACTIONS = ENVELOPE_INTERSECT%INTERSECTS%CONTAINS%CROSSES%DISJOINT%EQUALS%OVERLAPS%TOUCHES%WITHIN
    DATASET = $(mitOmraade)
    COMBINE_GEOM = Keep result geometry only
    COMBINE_ATTRS = Keep result attributes only
    FORMAT = FFS
    MitOmraade -> MyArea
    MitOmraade -> SpatialFilter [input 1]
MyArea: Inspector
SpatialFilter
    USE_BOUNDING_BOX = No
    MERGE_ATTRS = No
    BASE_TYPE = Multiple Bases
    PASS_CRITERIA = Pass Against One Base
    PREDATTR = _predicate
    PREDICATES = INTERSECTS
    CURVE_BOUNDARY_RULE_PARAM = Default Rule
    PASSED -> Fundet
    FAILED -> Sampler
Fundet: Inspector
Sampler
    RATE = 1
    SAMPLE_TYPE_LONG = First N Features
    SAMPLED -> TclCaller_4

Bookmark: Get and read the first GML file
TclCaller_4
    VAL_ATTR = _result
    TCLPROG = insertUserPass
    SRC:
      proc insertUserPass {} {

           set url [ FME_GetAttribute LinkURI ]
           set a [string range $url 0 5 ]
           set b [string range $url 6 end ]

           FME_SetAttribute LinkURI $a$::FME_MacroValues(user):$::FME_MacroValues(pass)@$b
           FME_Execute Log insertUserPass 0 2

           return

      }
    -> HTTPFetcher_2
HTTPFetcher_2
    TARGET_URL = @Value(LinkURI)
    STATUS_CODE_ATTR = _http_status_code
    SAVE_FILE = Yes
    PROXY_AUTH_METHOD = Basic
    FOLLOW_REDIRECTS = Yes
    OUTPUT_FILENAME = $(tempData)
    RESPONSE_HEADER_LIST_ATTR = _headers
    ERROR_ATTR = _error
    USE_COOKIES = No
    VERIFY_SSL_CERTIFICATES = Yes
    AUTH_METHOD = Basic
    TARGET_ATTR = _url_contents
    -> TclCaller_3
    <REJECTED> -> Logger__REJECTED_
TclCaller_3
    VAL_ATTR = _result
    TCLPROG = "7zip::unZip "
    SRC = source $FME_MacroValues(mfRoot)/7Zip/7zip.tcl
    NEW_ATTRIBUTES = fme_feature_fype
    -> Logger_3
    -> FeatureReader_2
FeatureReader_2
    GML_ADD_NAMESPACE_PREFIX_TO_NAMES = NO
    GML_MAP_GEOMETRY_COLUMNS = YES
    FEATURETYPES = Centroide Ejerlav Fredskov FredskovLinie Jordrente Jordstykke Klitfredning KlitfredningLinie MajoratSkov MatrikelSkel OptagetVej SkelPunkt Stormfald Strandbeskyttelse StrandbeskyttelseLinie
    GML_GML_EXPOSE_FORMAT_ATTRS = fme_feature_type,xml_char(50)
    GML_FLATTEN_XML_FRAGMENTS = NO
    COMBINE_GEOM = Keep result geometry only
    GML_SKIP_SCHEMA_LOCATION_IN_DATASET = No
    GML_DISABLE_XML_NAMESPACE_PROCESSING = NO
    GML_FEATURE_TYPES_SCHEMA_MODE = XML_SCHEMA
    COMBINE_ATTRS = Keep result attributes only
    GML_MAP_ALL_SUBSTITUTABLE_PROPERTIES = YES
    GML_VALIDATE_DATASET = no
    SUPPORTED_SPATIAL_INTERACTIONS = ENVELOPE_INTERSECT%INTERSECTS%CONTAINS%CROSSES%DISJOINT%EQUALS%OVERLAPS%TOUCHES%WITHIN
    GML_MAP_EMBEDDED_OBJECTS_AS = ATTRIBUTES
    GML_XML_FRAGMENTS_AS_DOCUMENTS = YES
    DATASET = $(gmlFile)
    ATTRIBUTES = Centroide,"gml_parent_id,gml_id,featureID,featureCode,featureType,ejerlavsnavn,landsejerlavskode,matrikelnummer,jordstykkeID,kms_SagsID,kms_Journalnummer,timeOfCreation,gml_pointProperty,gml_multiPointProperty",Ejerlav,"gml_parent_id,gml_id,featureID,featureCode,featureType,ejerlavsnavn,landsejerlavskode,timeOfCreation,gml_surfaceProperty,gml_multiSurfaceProperty",Fredskov,"gml_parent_id,gml_id,featureID,featureCode,featureType,ejerlavsnavn,landsejerlavskode,matrikelnummer,jordstykkeID,temaOmfang,areal,timeOfCreation,gml_surfaceProperty,gml_multiSurfaceProperty",FredskovLinie,"gml_parent_id,gml_id,featureID,temaFladeId,featureCode,featureType,kms_SagsID,kms_Journalnummer,matrikelSkelID,forloeb,timeOfCreation,gml_curveProperty,gml_multiCurveProperty",Jordrente,"gml_parent_id,gml_id,featureID,featureCode,featureType,ejerlavsnavn,landsejerlavskode,matrikelnummer,jordstykkeID,temaOmfang,timeOfCreation,gml_surfaceProperty,gml_multiSurfaceProperty",Jordstykke,"gml_parent_id,gml_id,featureID,featureCode,featureType,ejerlavsnavn,landsejerlavskode,matrikelnummer,kms_SagsID,kms_Journalnummer,skelforretningsSagsID,supmSagsID,kommunenavn,kommunekode,sognenavn,sognekode,regionsnavn,regionskode,retskredsnavn,retskredskode,moderjordstykke,registreretAreal,arealBeregn,vejAreal,vejArealBeregn,vandArealBeregn,faelleslod,harSamletFastEjendom.SFESamletFastEjendom.esr_Ejendomsnummer,harSamletFastEjendom.SFESamletFastEjendom.sfe_Ejendomsnummer,harSamletFastEjendom.SFESamletFastEjendom.sfe_SagsID,harSamletFastEjendom.SFESamletFastEjendom.sfe_Registreringsdato,harSamletFastEjendom.SFESamletFastEjendom.sfe_Journalnummer,harSamletFastEjendom.SFESamletFastEjendom.sfe_Registrering,harSamletFastEjendom.SFESamletFastEjendom.l_NoteringsType,arealType,registreringsdato,geometridato,timeOfCreation,gml_surfaceProperty,gml_multiSurfaceProperty",Klitfredning,"gml_parent_id,gml_id,featureID,featureCode,featureType,ejerlavsnavn,landsejerlavskode,matrikelnummer,jordstykkeID,temaOmfang,areal,timeOfCreation,gml_surfaceProperty,gml_multiSurfaceProperty",KlitfredningLinie,"gml_parent_id,gml_id,featureID,temaFladeId,featureCode,featureType,kms_SagsID,kms_Journalnummer,matrikelSkelID,forloeb,timeOfCreation,gml_curveProperty,gml_multiCurveProperty",MajoratSkov,"gml_parent_id,gml_id,featureCode,featureType,ejerlavsnavn,landsejerlavskode,matrikelnummer,jordstykkeID,temaOmfang,ms_SkovNr,timeOfCreation,gml_surfaceProperty,gml_multiSurfaceProperty",MatrikelSkel,"gml_parent_id,gml_id,featureID,featureCode,featureType,kms_SagsID,kms_Journalnummer,oprindelsesJournalNr,skelforretningsSagsID,dq_ProdMetode,adm_Status,fra_PunktID,til_PunktID,left_JordstykkeID,right_JordstykkeID,timeOfCreation,gml_curveProperty,gml_multiCurveProperty",OptagetVej,"gml_parent_id,gml_id,featureID,featureCode,featureType,ejerlavsnavn,landsejerlavskode,matrikelnummer,jordstykkeID,kms_SagsID,kms_Journalnummer,vejbredde,vejtype,dq_ProdMetode,timeOfCreation,gml_curveProperty,gml_multiCurveProperty",SkelPunkt,"gml_parent_id,gml_id,featureID,featureCode,featureType,kms_SagsID,kms_Journalnummer,oprindelsesJournalNr,supmSagsID,dq_ProdMetode,dq_IndlType,dq_Punktklasse,timeOfCreation,gml_pointProperty,gml_multiPointProperty",Stormfald,"gml_parent_id,gml_id,featureCode,featureType,ejerlavsnavn,landsejerlavskode,matrikelnummer,jordstykkeID,temaOmfang,sf_Registrering,sf_Betalingsdato,sf_Ophoersdato,sf_SNS_JournalNr,timeOfCreation,gml_surfaceProperty,gml_multiSurfaceProperty",Strandbeskyttelse,"gml_parent_id,gml_id,featureID,featureCode,featureType,ejerlavsnavn,landsejerlavskode,matrikelnummer,jordstykkeID,temaOmfang,areal,timeOfCreation,gml_surfaceProperty,gml_multiSurfaceProperty",StrandbeskyttelseLinie,"gml_parent_id,gml_id,featureID,temaFladeId,featureCode,featureType,kms_SagsID,kms_Journalnummer,matrikelSkelID,forloeb,timeOfCreation,gml_curveProperty,gml_multiCurveProperty"
    GML_USE_OLD_READER = NO
    GML_USE_PROXY = NO
    GML_MAP_COMPLEX_PROPERTIES_AS = Nested Attributes
    FORMAT = GML
    GML_READ_PREDEFINED_GML_PROPERTIES = NO
    SkelPunkt -> DataLaest [off]
    MatrikelSkel -> DataLaest [off]
    Centroide -> DataLaest
    Ejerlav -> DataLaest
    Fredskov -> DataLaest
    FredskovLinie -> DataLaest
    Jordrente -> DataLaest
    Jordstykke -> DataLaest
    Klitfredning -> DataLaest
    KlitfredningLinie -> DataLaest
    MajoratSkov -> DataLaest
    OptagetVej -> DataLaest
    Stormfald -> DataLaest
    Strandbeskyttelse -> DataLaest
    StrandbeskyttelseLinie -> DataLaest
DataLaest: Inspector
Logger_3
    MESSAGE = Feature is:
    MAXFEATS = 20
    MAXCOORDS = 20
Logger__REJECTED_
    MESSAGE = Feature is:
    MAXFEATS = 20
    MAXCOORDS = 20
